(defun c:foo (/ el h p p2 pl s sp x)
  ;; RJP » 2021-07-07
  ;; Converts solids to hatches
  (if (setq s (ssget "_X" '((0 . "SOLID"))))
    (progn
      (foreach e (mapcar 'cadr (ssnamex s))
	(setq el (entget e))
	(setq sp (vlax-ename->vla-object (cdr (assoc 330 el))))
	(setq p (mapcar 'cdr (vl-remove-if-not '(lambda (x) (member (car x) '(10 11 12 13))) el)))
	(setq p2 (list (car p) (cadr p) (last p) (caddr p)))
	(setq pl (entmakex (apply 'append
				  (list	(list '(0 . "LWPOLYLINE")
					      '(100 . "AcDbEntity")
					      (assoc 8 el)
					      (cons 100 "AcDbPolyline")
					      '(90 . 4)
					      '(70 . 1)
					)
					(mapcar '(lambda (x) (list 10 (car x) (cadr x))) p2)
				  )
			   )
		 )
	)
	(setq h (vlax-invoke sp 'addhatch achatchobject "SOLID" :vlax-true))
	(vlax-invoke h 'appendouterloop (list (vlax-ename->vla-object pl)))
	(vla-put-layer h (cdr (assoc 8 el)))
	(entdel e)
      )
    )
  )
  (princ)
)
