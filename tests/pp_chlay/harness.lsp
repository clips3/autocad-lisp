;; Regression tests run ONLY in the disposable drawing started by run.py.
;; No mocks of AutoCAD, ActiveX, entget, entmod or ssget.
(vl-load-com)

(defun pp-test:emit (key value)
  (prin1 (list key value) *pp-test-output*)
  (write-line "" *pp-test-output*)
)

(defun pp-test:must (condition message)
  (if (not condition)
    (progn (pp-test:emit "fatal" message) (/ 1 0))
  )
)

(defun pp-test:layer (name / layers)
  (if (not (tblsearch "LAYER" name))
    (progn
      (setq layers (vla-get-layers *pp-test-doc*))
      (vla-add layers name)
    )
  )
)

(defun pp-test:tag (ent id / data)
  (setq data (entget ent))
  (entmod (append data (list (list -3 (list "PP_CHLAY_TEST" (cons 1000 id))))))
  ent
)

(defun pp-test:id (ent / data)
  (setq data (assoc -3 (entget ent '("PP_CHLAY_TEST"))))
  (if data (cdr (assoc 1000 (cdr (cadr data)))))
)

(defun pp-test:poly (layer x closed / ent)
  (setq ent
    (entmakex
      (list '(0 . "LWPOLYLINE") '(100 . "AcDbEntity") (cons 8 layer)
        '(100 . "AcDbPolyline") '(90 . 4) (cons 70 closed)
        (cons 10 (list x 0.0)) (cons 10 (list (+ x 2.0) 0.0))
        (cons 10 (list (+ x 2.0) 3.0)) (cons 10 (list x 3.0))
      )
    )
  )
  (pp-test:must ent "Could not create test polyline")
  ent
)

(defun pp-test:make (case index / id layer kind ent x boundary hatch loop obj)
  (setq id (nth 0 case) layer (nth 1 case) kind (nth 2 case) x (* index 10.0))
  (pp-test:layer layer)
  (setq ent
    (cond
      ((= kind "LINE")
        (entmakex (list '(0 . "LINE") (cons 8 layer)
          (cons 10 (list x 0.0 0.0)) (cons 11 (list (+ x 2.0) 3.0 0.0)))))
      ((= kind "TEXT")
        (entmakex (list '(0 . "TEXT") (cons 8 layer)
          (cons 10 (list x 0.0 0.0)) '(40 . 0.2) '(1 . "fixture"))))
      ((= kind "MTEXT")
        (entmakex (list '(0 . "MTEXT") '(100 . "AcDbEntity") (cons 8 layer)
          '(100 . "AcDbMText") (cons 10 (list x 0.0 0.0))
          '(40 . 0.2) '(41 . 3.0) '(1 . "fixture"))))
      ((= kind "POLY_OPEN") (pp-test:poly layer x 0))
      ((= kind "POLY_CLOSED") (pp-test:poly layer x 1))
      ((= kind "HATCH")
        (setq boundary (pp-test:poly layer x 1))
        (setq hatch (vla-AddHatch (vla-get-modelspace *pp-test-doc*) 1 "SOLID" :vlax-false))
        (setq loop (vlax-make-safearray vlax-vbObject '(0 . 0)))
        (vlax-safearray-put-element loop 0 (vlax-ename->vla-object boundary))
        (vla-AppendOuterLoop hatch loop)
        (vla-Evaluate hatch)
        (vla-put-layer hatch layer)
        (entdel boundary)
        (vlax-vla-object->ename hatch))
    )
  )
  (pp-test:must ent (strcat "Could not create fixture: " id))
  ;; Deliberate overrides let the snapshots detect lost ByLayer resets.
  (setq obj (vlax-ename->vla-object ent))
  (vla-put-color obj 3)
  (vla-put-linetype obj "Continuous")
  (vla-put-linetypescale obj 2.0)
  (vla-put-lineweight obj 25)
  (pp-test:tag ent id)
)

(defun pp-test:fixtures (cases / selection index case)
  (setq selection (ssadd) index 0)
  (foreach case cases
    (ssadd (pp-test:make case index) selection)
    (setq index (1+ index))
  )
  selection
)

(defun pp-test:properties (ent / data code result value obj pair)
  (setq data (entget ent) result nil)
  ;; Stable DXF fields; handles, enames and owners intentionally excluded.
  ;; Keep all occurrences of 10/11 to capture every polyline vertex.
  (foreach code '(0 8 62 6 48 370 440 70 2 41 52 10 11 38 39 210 67 410)
    (setq value nil)
    (foreach pair data
      (if (= (car pair) code) (setq value (cons (cdr pair) value)))
    )
    (setq result (cons (list code (reverse value)) result))
  )
  (if (= (cdr (assoc 0 data)) "HATCH")
    (progn
      (setq obj (vlax-ename->vla-object ent))
      (setq result (cons (list "hatch" (vla-get-PatternName obj)
        (vla-get-PatternScale obj) (vla-get-PatternAngle obj) (vla-get-Area obj)) result))
    )
  )
  (reverse result)
)

(defun pp-test:snapshot (phase / ss index ent id unexpected)
  (setq ss (ssget "_X" '((410 . "Model"))) index 0 unexpected 0)
  (if ss
    (while (< index (sslength ss))
      (setq ent (ssname ss index) id (pp-test:id ent))
      (if id
        (pp-test:emit (strcat phase "/" id) (pp-test:properties ent))
        (progn
          ;; Hatch creation adds entities without inheriting boundary XData.
          ;; Observe them before tagging solely for safe fixture cleanup.
          (pp-test:emit (strcat phase "/created") (pp-test:properties ent))
          (setq unexpected (1+ unexpected))
          (pp-test:tag ent "generated")
        )
      )
      (setq index (1+ index))
    )
  )
  (pp-test:emit (strcat phase "/untagged") unexpected)
)

(defun pp-test:clear (/ ss index ent)
  ;; Refuse to remove anything we did not create.
  (setq ss (ssget "_X" '((410 . "Model"))) index 0)
  (if ss
    (while (< index (sslength ss))
      (setq ent (ssname ss index))
      (pp-test:must (pp-test:id ent) "Untagged object in disposable drawing")
      (entdel ent)
      (setq index (1+ index))
    )
  )
)

(defun pp-test:settings (phase / name)
  (foreach name '("CMDECHO" "HIGHLIGHT" "LTSCALE" "CLAYER" "CETRANSPARENCY")
    (pp-test:emit (strcat phase "/sysvar/" name) (getvar name))
  )
)

(defun pp-test:reset ()
  (setq *chlay-canonical-cache* nil *chlay-verified-layers* nil)
  (setvar "CLAYER" "0")
  (setvar "CMDECHO" 1)
  (setvar "HIGHLIGHT" 1)
  (setvar "LTSCALE" 1.0)
  (setvar "CETRANSPARENCY" -1)
)

(defun pp-test:layers (/ definition name data layer)
  (foreach definition (chlay:get-predefined-layers)
    (setq name (car definition) data (tblsearch "LAYER" name))
    (setq layer (vla-item (vla-get-layers *pp-test-doc*) name))
    (pp-test:emit (strcat "layers/" name)
      (list (cdr (assoc 62 data)) (cdr (assoc 6 data)) (vla-get-Plottable layer)))
  )
)

(defun pp-test:run-body (/ selection case index result before ent)
  (setq *pp-test-doc* (vla-get-activedocument (vlax-get-acad-object)))
  (pp-test:must (= 0 (getvar "DWGTITLED")) "Tests require a NEW unsaved drawing")
  (pp-test:must (not (ssget "_X" '((410 . "Model")))) "Tests require an EMPTY ModelSpace")
  (regapp "PP_CHLAY_TEST")
  (pp-test:reset)
  ;; Pure helpers exercise the actual loaded functions, including XREF names
  ;; that cannot be created as ordinary local layer names.
  (setq index 0)
  (foreach case *pp-test-matches*
    (pp-test:emit (strcat "match/" (itoa index))
      (chlay:layer-matches-p (car case) (cadr case)))
    (setq index (1+ index))
  )
  (foreach case *pp-test-helpers*
    (pp-test:emit (strcat "base/" case) (chlay:get-base-layer case))
    (pp-test:emit (strcat "norm/" case) (chlay:norm-str case))
  )
  (foreach case '("pp_pilar" "pp_projecao" "PP_VEGETACAO" "PP_CUSTOM_TEST")
    (pp-test:emit (strcat "canonical/" case) (chlay:get-canonical-layer case))
  )
  ;; Actual CHLAUTO implementation, with the rules inside the production code.
  (setq selection (pp-test:fixtures *pp-test-cases*))
  (setq before (getvar "MILLISECS"))
  (chlay:clean-selection selection)
  (pp-test:emit "timing/clean-ms" (- (getvar "MILLISECS") before))
  (pp-test:snapshot "clean")
  (pp-test:settings "clean")
  (pp-test:layers)
  (pp-test:clear)
  ;; Actual CHLDEL implementation on exactly the same original fixtures.
  (pp-test:reset)
  (setq selection (pp-test:fixtures *pp-test-cases*))
  (setq before (getvar "MILLISECS"))
  (chlay:delete-selection selection)
  (pp-test:emit "timing/delete-ms" (- (getvar "MILLISECS") before))
  (pp-test:snapshot "delete")
  (pp-test:settings "delete")
  (pp-test:clear)
  ;; Manual CHL destinations, independent of automatic classification.
  (foreach case '("PP_ARQUITETURA" "PP_PILAR" "PP_FORRO" "PP_VEGETACAO" "PP_CUSTOM_TEST")
    (pp-test:reset)
    (setq selection (pp-test:fixtures *pp-test-manual*))
    (chlay:apply-layer selection case)
    (pp-test:snapshot (strcat "manual/" case))
    (pp-test:settings (strcat "manual/" case))
    (pp-test:clear)
  )
  ;; Repeated formatting records current idempotence (or lack of it).
  (pp-test:reset)
  (setq ent (pp-test:make '("repeat-hatch" "PP_PILAR" "HATCH") 0))
  (chlay:move-entity ent "PP_PILAR")
  (pp-test:snapshot "pillar-once")
  (chlay:move-entity ent "PP_PILAR")
  (pp-test:snapshot "pillar-twice")
  (chlay:deduplicate-hatches "PP_PILAR")
  (pp-test:snapshot "pillar-deduplicated")
  (pp-test:clear)
  ;; Actual interactive CHLHATCH entry point with implied selection, so no
  ;; simulated selection APIs are needed. The remote hatch is a scope sentinel.
  (pp-test:reset)
  (setq selection (ssadd (pp-test:make '("selected-pillar" "PP_PILAR" "POLY_OPEN") 0)))
  (pp-test:make '("outside-selection" "PP_ARQUITETURA" "HATCH") 20)
  (setvar "PICKFIRST" 1)
  (sssetfirst nil selection)
  (c:CHLHATCH)
  (sssetfirst nil nil)
  (pp-test:snapshot "hatch-command")
  (pp-test:settings "hatch-command")
  (pp-test:clear)
  T
)

(defun pp-test:run (output / result saved name item)
  (foreach name '("PICKFIRST" "HIGHLIGHT" "CMDECHO" "CLAYER" "LTSCALE" "CETRANSPARENCY")
    (setq saved (cons (cons name (getvar name)) saved))
  )
  (setq *pp-test-output* (open output "w" "utf8"))
  (pp-test:must *pp-test-output* "Cannot open test output")
  (pp-test:emit "environment" (list (getvar "ACADVER") (getvar "LISPSYS")))
  (setq result (vl-catch-all-apply 'pp-test:run-body nil))
  (if (vl-catch-all-error-p result)
    (pp-test:emit "fatal" (vl-catch-all-error-message result))
    (pp-test:emit "complete" T)
  )
  (foreach item saved
    (vl-catch-all-apply 'setvar (list (car item) (cdr item)))
  )
  (close *pp-test-output*)
  (setq *pp-test-output* nil)
  (princ)
)
