;; Independent behavioral assertions for intentional fixes and optimized paths.
;; Loaded only when checking the candidate; the original golden stays frozen.
(defun pp-contract:check (name condition)
  (pp-test:emit (strcat "contracts/" name) (if condition T nil))
)
(defun pp-contract:poly (id layer vertices z / data vertex ent)
  (pp-test:layer layer)
  (setq data (list '(0 . "LWPOLYLINE") '(100 . "AcDbEntity") (cons 8 layer)
    '(100 . "AcDbPolyline") (cons 90 (length vertices)) '(70 . 1) (cons 38 z)))
  (foreach vertex vertices
    (setq data (append data (list (cons 10 (list (car vertex) (cadr vertex)))
      (cons 42 (if (caddr vertex) (caddr vertex) 0.0))))))
  (setq ent (entmakex data))
  (pp-test:must ent "Could not create contract polyline")
  (pp-test:tag ent id)
)
(defun pp-contract:hatch (id vertices z holes / boundary hatch loop inner ent)
  (setq boundary (pp-contract:poly "boundary" "PP_ARQUITETURA" vertices z)
        hatch (vla-AddHatch (vla-get-ModelSpace *pp-test-doc*) 1 "SOLID" :vlax-false)
        loop (vlax-make-safearray vlax-vbObject '(0 . 0)))
  (vlax-safearray-put-element loop 0 (vlax-ename->vla-object boundary))
  (vla-AppendOuterLoop hatch loop)
  (foreach vertices holes
    (setq inner (pp-contract:poly "inner-boundary" "PP_ARQUITETURA" vertices z))
    (vlax-safearray-put-element loop 0 (vlax-ename->vla-object inner))
    (vla-AppendInnerLoop hatch loop)
    (entdel inner))
  (vla-put-Elevation hatch z)
  (vla-Evaluate hatch)
  (vla-put-Layer hatch "PP_ARQUITETURA")
  (entdel boundary)
  (setq ent (vlax-vla-object->ename hatch))
  (pp-test:tag ent id)
)
(defun pp-contract:pair (id1 shape1 z1 holes1 id2 shape2 z2 holes2 / a b selection)
  (setq a (pp-contract:hatch id1 shape1 z1 holes1)
        b (pp-contract:hatch id2 shape2 z2 holes2)
        selection (ssadd b (ssadd a)))
  (list a b selection)
)
(defun pp-contract:count-hatches ()
  (if (ssget "_X" '((0 . "HATCH") (410 . "Model")))
    (sslength (ssget "_X" '((0 . "HATCH") (410 . "Model")))) 0)
)
(defun pp-contract:draw-order (/ dictionary table objects)
  (setq dictionary (vla-GetExtensionDictionary (vla-get-ModelSpace *pp-test-doc*))
        table (vla-GetObject dictionary "ACAD_SORTENTS"))
  (vla-GetFullDrawOrder table 'objects :vlax-false)
  (if (= (type objects) 'VARIANT) (setq objects (vlax-variant-value objects)))
  (mapcar 'vlax-vla-object->ename (vlax-safearray->list objects))
)
(defun pp-contract:geometry (/ pair a b selection shape rect0 rect1 holes0 holes1 copied array paper owner)
  ;; Same bounding box and area, different actual contours.
  (setq pair (pp-contract:pair "triangle-a" '((0.0 0.0) (2.0 0.0) (2.0 3.0)) 0.0 nil
                              "triangle-b" '((0.0 0.0) (2.0 0.0) (0.0 3.0)) 0.0 nil))
  (pp-contract:check "distinct-triangles-have-distinct-keys"
    (/= (chlay:get-hatch-sig (car pair)) (chlay:get-hatch-sig (cadr pair))))
  (pp-contract:check "same-box-and-area-does-not-delete-geometry"
    (and (= 0 (chlay:deduplicate-selection (caddr pair) nil)) (= 2 (pp-contract:count-hatches))))
  (pp-test:clear)
  (setq rect0 '((0.0 0.0) (4.0 0.0) (4.0 4.0) (0.0 4.0))
        rect1 '((0.001 0.0) (4.001 0.0) (4.001 4.0) (0.001 4.0)))
  (setq pair (pp-contract:pair "near-a" rect0 0.0 nil "near-b" rect1 0.0 nil))
  (pp-contract:check "nearby-contours-remain-distinct"
    (and (/= (chlay:get-hatch-sig (car pair)) (chlay:get-hatch-sig (cadr pair)))
         (= 0 (chlay:deduplicate-selection (caddr pair) nil))))
  (pp-test:clear)
  (setq pair (pp-contract:pair "elevation-a" rect0 0.0 nil "elevation-b" rect0 1.0 nil))
  (pp-contract:check "elevation-is-part-of-the-key"
    (and (/= (chlay:get-hatch-sig (car pair)) (chlay:get-hatch-sig (cadr pair)))
         (= 0 (chlay:deduplicate-selection (caddr pair) nil))))
  (pp-test:clear)
  (setq holes0 '(((0.5 0.5) (1.5 0.5) (1.5 1.5) (0.5 1.5)))
        holes1 '(((2.5 2.5) (3.5 2.5) (3.5 3.5) (2.5 3.5))))
  (setq pair (pp-contract:pair "islands-a" rect0 0.0 holes0 "islands-b" rect0 0.0 holes1))
  (pp-contract:check "island-contours-are-not-ignored"
    (and (/= (chlay:get-hatch-sig (car pair)) (chlay:get-hatch-sig (cadr pair)))
         (= 0 (chlay:deduplicate-selection (caddr pair) nil))))
  (pp-test:clear)
  ;; Opposite orientation / different starting vertex of the same contour.
  (setq pair (pp-contract:pair "duplicate-a" rect0 0.0 nil
    "duplicate-b" '((4.0 4.0) (4.0 0.0) (0.0 0.0) (0.0 4.0)) 0.0 nil))
  (pp-contract:check "same-ring-normalizes-direction-and-start"
    (= (chlay:get-hatch-sig (car pair)) (chlay:get-hatch-sig (cadr pair))))
  (pp-contract:check "actual-duplicates-are-removed"
    (and (= 1 (chlay:deduplicate-selection (caddr pair) nil)) (= 1 (pp-contract:count-hatches))))
  (pp-test:clear)
  ;; Identical geometry in a different owner/layout must be kept.
  (setq a (pp-contract:hatch "model-hatch" rect0 0.0 nil)
        array (vlax-make-safearray vlax-vbObject '(0 . 0)))
  (vlax-safearray-put-element array 0 (vlax-ename->vla-object a))
  (setq copied (vla-CopyObjects *pp-test-doc* array (vla-get-PaperSpace *pp-test-doc*)))
  (setq paper (car (vlax-safearray->list (vlax-variant-value copied)))
        b (vlax-vla-object->ename paper))
  (pp-contract:check "layout-is-part-of-the-key" (/= (chlay:get-hatch-sig a) (chlay:get-hatch-sig b)))
  (setq selection (ssadd b (ssadd a)))
  (pp-contract:check "other-layout-is-never-deduplicated-with-model"
    (and (= 0 (chlay:deduplicate-selection selection nil)) (entget a) (entget b)))
  (vla-Delete paper)
  (pp-test:clear)
)
(defun pp-contract:pillars (/ ent hatch sig selection result first-count after-count array order solid ansi item)
  (setq ent (pp-test:make '("open-pillar" "S-COLS" "POLY_OPEN") 0))
  (chlay:clean-selection (ssadd ent))
  (pp-contract:check "closing-pillar-keeps-new-layer-and-bylayer"
    (and (= (cdr (assoc 8 (entget ent))) "PP_PILAR")
         (= 1 (logand 1 (cdr (assoc 70 (entget ent)))))
         (not (assoc 62 (entget ent))) (not (assoc 6 (entget ent)))
         (not (assoc 48 (entget ent))) (not (assoc 370 (entget ent)))))
  (setq hatch (chlay:create-polyline-hatch ent))
  (pp-test:tag hatch "pillar-hatch")
  (vla-put-Layer (vlax-ename->vla-object hatch) "PP_PILAR")
  (pp-contract:check "polyline-and-hatch-share-the-same-geometry-key"
    (= (chlay:get-pline-sig ent) (chlay:get-hatch-sig hatch)))
  (setq selection (ssadd ent))
  (chlay:with-operation 'chlay:hatch-selection (list selection) T)
  (setq first-count (pp-contract:count-hatches))
  (setq result (chlay:with-operation 'chlay:hatch-selection (list selection) T))
  (pp-contract:check "second-hatch-run-creates-no-new-fill"
    (and (= (cadr result) 0) (= 2 first-count) (= 2 (pp-contract:count-hatches))))
  (chlay:move-entity hatch "PP_PILAR") (chlay:move-entity hatch "PP_PILAR")
  (pp-contract:check "direct-formatting-is-idempotent" (= 2 (pp-contract:count-hatches)))
  (setq order (pp-contract:draw-order))
  (foreach item order
    (if (= (cdr (assoc 0 (entget item))) "HATCH")
      (if (= (cdr (assoc 2 (entget item))) "SOLID") (setq solid item) (setq ansi item))))
  (pp-contract:check "ansi37-is-drawn-above-solid"
    (and solid ansi (member ansi (cdr (member solid order)))))
  (pp-test:clear)
  ;; A closed two-vertex polyline with two semicircles is a valid circle.
  (setq ent (pp-contract:poly "curved-pillar" "PP_PILAR" '((0.0 0.0 1.0) (2.0 0.0 1.0)) 0.0)
        hatch (chlay:create-polyline-hatch ent))
  (pp-contract:check "curved-polyline-creates-valid-hatch" (and hatch (entget hatch)))
  (if hatch
    (progn
      (pp-test:tag hatch "curved-hatch")
      (pp-contract:check "curved-polyline-matches-hatch-contour"
        (= (chlay:get-pline-sig ent) (chlay:get-hatch-sig hatch)))))
  (pp-test:clear)
  ;; Zero-area / invalid loops must leave no half-created hatch behind.
  (setq ent (pp-contract:poly "invalid-loop" "PP_PILAR" '((0.0 0.0) (1.0 0.0) (2.0 0.0)) 0.0))
  (pp-contract:check "invalid-loop-leaves-no-orphan-hatch"
    (and (not (chlay:create-polyline-hatch ent)) (= 0 (pp-contract:count-hatches))))
  (pp-test:clear)
)
(defun pp-contract:scope (/ outside inside selection before after result)
  (setq outside (pp-test:make '("unselected" "PP_ARQUITETURA" "HATCH") 10)
        before (pp-test:properties outside)
        inside (pp-test:make '("selected" "PP_PILAR" "POLY_OPEN") 0)
        selection (ssadd inside))
  (chlay:with-operation 'chlay:hatch-selection (list selection) T)
  (pp-contract:check "hatch-command-preserves-unselected-objects"
    (equal before (pp-test:properties outside)))
  ;; Main fixtures normally tag generated entities during their snapshot.
  (pp-test:snapshot "contract-cleanup")
  (pp-test:clear)
  (setq outside (pp-test:make '("manual-unselected" "PP_PILAR" "HATCH") 20)
        before (pp-test:properties outside)
        inside (pp-test:make '("manual-selected" "ZZ_MANUAL_TEST" "LINE") 0))
  (chlay:apply-layer (ssadd inside) "PP_PILAR")
  (pp-contract:check "manual-command-preserves-remote-pillar-hatch"
    (equal before (pp-test:properties outside)))
  (pp-test:clear)
)
(defun pp-contract:runtime (/ tree i ok key value old-del old-map ent layer selection result saved name state color a b order)
  (setq i 0 ok T)
  (repeat 1024
    (setq key (strcat "KEY-" (itoa i)) tree (chlay:map-put tree key i) i (1+ i)))
  (setq i 0)
  (repeat 1024
    (if (/= (cdr (chlay:map-get tree (strcat "KEY-" (itoa i)))) i) (setq ok nil))
    (setq i (1+ i)))
  (pp-contract:check "cache-lookup-preserves-all-values" ok)
  (pp-contract:check "cache-remains-balanced" (<= (chlay:height tree) 16))
  (setq tree (chlay:map-put tree "NIL-VALUE" nil))
  (pp-contract:check "cache-distinguishes-missing-from-nil" (chlay:map-get tree "NIL-VALUE"))
  (pp-contract:check "shared-rules-have-original-counts"
    (and (= 124 (length (chlay:rules-delete))) (= 404 (length (chlay:rules-map)))))
  (setq old-del del_pat old-map map_entry del_pat "sentinel-del" map_entry "sentinel-map")
  (chlay:resolve-layer-action "A-WALL" nil nil)
  (pp-contract:check "matcher-does-not-leak-loop-variables"
    (and (= del_pat "sentinel-del") (= map_entry "sentinel-map")))
  (setq del_pat old-del map_entry old-map)
  ;; Validate cleanup after a real LISP exception inside a grouped operation.
  (setvar "CMDECHO" 1) (setvar "HIGHLIGHT" 1) (setvar "LTSCALE" 7.0)
  (foreach name '("CMDECHO" "HIGHLIGHT" "LTSCALE" "CLAYER" "CETRANSPARENCY")
    (setq saved (cons (cons name (getvar name)) saved)))
  (setq state (logand 8 (getvar "UNDOCTL")))
  (setq result (chlay:with-operation
    '(lambda () (setvar "CMDECHO" 0) (setvar "HIGHLIGHT" 0)
       (setvar "LTSCALE" 99.0) (setvar "CETRANSPARENCY" 39) (/ 1 0)) nil nil))
  (setq ok T)
  (foreach value saved (if (not (equal (getvar (car value)) (cdr value))) (setq ok nil)))
  (pp-contract:check "error-restores-all-system-variables" (and (not result) ok))
  (pp-contract:check "error-closes-undo-group" (= state (logand 8 (getvar "UNDOCTL"))))
  (setq ent (pp-test:make '("locked-object" "PP_TEST_LOCKED" "LINE") 0)
        layer (vla-item (vla-get-Layers *pp-test-doc*) "PP_TEST_LOCKED"))
  (vla-put-Lock layer :vlax-true)
  (setq saved (entget ent))
  (chlay:apply-layer (ssadd ent) "PP_LAYOUT")
  (pp-contract:check "locked-source-keeps-original-without-copy"
    (and (equal saved (entget ent)) (= 1 (sslength (ssget "_X" '((410 . "Model")))))))
  (vla-put-Lock layer :vlax-false)
  (pp-test:clear)
  (setq ent (pp-test:make '("locked-pillar" "S-COLS" "POLY_OPEN") 0)
        layer (vla-item (vla-get-Layers *pp-test-doc*) "S-COLS") saved (entget ent))
  (vla-put-Lock layer :vlax-true)
  (chlay:clean-selection (ssadd ent))
  (pp-contract:check "failed-pillar-move-does-not-close-original"
    (and (equal saved (entget ent)) (= 0 (logand 1 (cdr (assoc 70 (entget ent)))))))
  (vla-put-Lock layer :vlax-false)
  (pp-test:clear)
  ;; Purging a previously used target must not invalidate a document cache.
  (setq ent (pp-test:make '("first-target" "ZZ_MANUAL_TEST" "LINE") 0))
  (chlay:apply-layer (ssadd ent) "PP_TEST_RECREATED")
  (pp-test:clear)
  (vla-Delete (vla-item (vla-get-Layers *pp-test-doc*) "PP_TEST_RECREATED"))
  (setq ent (pp-test:make '("second-target" "ZZ_MANUAL_TEST" "LINE") 0))
  (chlay:apply-layer (ssadd ent) "PP_TEST_RECREATED")
  (pp-contract:check "target-cache-is-scoped-to-each-operation"
    (= "PP_TEST_RECREATED" (cdr (assoc 8 (entget ent)))))
  (pp-test:clear)
  (setq ent (pp-test:make '("truecolor-object" "ZZ_MANUAL_TEST" "LINE") 0)
        color (vla-get-TrueColor (vlax-ename->vla-object ent)))
  (vla-SetRGB color 27 63 91)
  (vla-put-TrueColor (vlax-ename->vla-object ent) color)
  (chlay:apply-layer (ssadd ent) "PP_LAYOUT")
  (pp-contract:check "bylayer-reset-removes-truecolor-override"
    (and (not (assoc 420 (entget ent))) (not (assoc 62 (entget ent)))
         (= "PP_LAYOUT" (cdr (assoc 8 (entget ent))))))
  (pp-test:clear)
  (setq layer (vla-item (vla-get-Layers *pp-test-doc*) "PP_LAYOUT") color (vla-get-TrueColor layer))
  (vla-SetRGB color 27 63 91) (vla-put-TrueColor layer color)
  (vla-put-Linetype layer "DASHED") (vla-put-Plottable layer :vlax-false)
  (c:PPLAYERS)
  (pp-contract:check "pplayers-restores-aci-linetype-and-plot"
    (and (= 253 (cdr (assoc 62 (tblsearch "LAYER" "PP_LAYOUT"))))
         (= "Continuous" (cdr (assoc 6 (tblsearch "LAYER" "PP_LAYOUT"))))
         (= :vlax-true (vla-get-Plottable layer))
         (not (assoc 420 (tblsearch "LAYER" "PP_LAYOUT")))))
  (setq a (pp-test:make '("front-layer" "PP_LAYOUT" "LINE") 0)
        b (pp-test:make '("back-layer" "PP_FORRO" "LINE") 1))
  (c:ORGL)
  (setq order (pp-contract:draw-order))
  (pp-contract:check "orgl-restores-command-state-and-order"
    (and (member a (cdr (member b order))) (= 1 (getvar "CMDECHO")) (= 1 (getvar "HIGHLIGHT"))))
  (pp-test:clear)
)
(defun pp-contract:patterns (/ h-veg h-proj h-lay vla-v vla-p vla-l)
  (setq h-veg (pp-test:make '("h-veg" "ZZ_MANUAL_TEST" "HATCH") 10)
        h-proj (pp-test:make '("h-proj" "ZZ_MANUAL_TEST" "HATCH") 20)
        h-lay (pp-test:make '("h-lay" "ZZ_MANUAL_TEST" "HATCH") 30))
  (chlay:apply-layer (ssadd h-veg) "PP_VEGETAÇÃO")
  (chlay:apply-layer (ssadd h-proj) "PP_PROJEÇÃO")
  (chlay:apply-layer (ssadd h-lay) "PP_LAYOUT")
  (setq vla-v (vlax-ename->vla-object h-veg)
        vla-p (vlax-ename->vla-object h-proj)
        vla-l (vlax-ename->vla-object h-lay))
  (pp-contract:check "hatch-vegetacao-pattern-and-scale"
    (and (= (strcase (vla-get-PatternName vla-v)) "GRASS")
         (equal (vla-get-PatternScale vla-v) 0.01 1e-4)
         (equal (vla-get-PatternAngle vla-v) 0.0 1e-4)
         (= (vla-get-EntityColor (vla-get-BackgroundColor vla-v)) -939524096)))
  (pp-contract:check "hatch-projecao-pattern-and-scale"
    (and (= (strcase (vla-get-PatternName vla-p)) "ANSI31")
         (equal (vla-get-PatternScale vla-p) 0.1 1e-4)
         (equal (vla-get-PatternAngle vla-p) 0.0 1e-4)
         (= (vla-get-EntityColor (vla-get-BackgroundColor vla-p)) -939524096)))
  (pp-contract:check "hatch-layout-pattern-and-scale"
    (and (= (strcase (vla-get-PatternName vla-l)) "ANSI37")
         (equal (vla-get-PatternScale vla-l) 0.02 1e-4)
         (equal (vla-get-PatternAngle vla-l) 0.0 1e-4)
         (= (vla-get-EntityColor (vla-get-BackgroundColor vla-l)) -939524096)))
  (pp-test:clear)
)
(defun pp-contract:body ()
  (pp-test:must (not (ssget "_X" '((410 . "Model")))) "Contract tests require empty scratch ModelSpace")
  (pp-contract:runtime)
  (pp-contract:geometry)
  (pp-contract:pillars)
  (pp-contract:scope)
  (pp-contract:patterns)
  T
)
(defun pp-contract:run (output / result name saved)
  (foreach name '("CMDECHO" "HIGHLIGHT" "LTSCALE" "CLAYER" "CETRANSPARENCY")
    (setq saved (cons (cons name (getvar name)) saved)))
  (setq *pp-test-output* (open output "w" "utf8"))
  (pp-test:emit "environment" (list (getvar "ACADVER") (getvar "LISPSYS")))
  (setq result (vl-catch-all-apply 'pp-contract:body nil))
  (if (vl-catch-all-error-p result)
    (pp-test:emit "fatal" (vl-catch-all-error-message result))
    (pp-test:emit "complete" T))
  (foreach name saved (vl-catch-all-apply 'setvar (list (car name) (cdr name))))
  (close *pp-test-output*) (setq *pp-test-output* nil)
  (princ)
)
