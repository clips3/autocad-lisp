;; Same workload for original/candidate, including a second already-formatted pass.
(defun pp-benchmark:body (count / i ent selection started)
  (pp-test:must (not (ssget "_X" '((410 . "Model")))) "Benchmark requires empty scratch drawing")
  (chlay:ensure-all-predefined-layers)
  (setq i 0)
  (repeat count
    (pp-test:make (list (strcat "hatch-" (itoa i)) "PP_FORRO" "HATCH") i)
    (setq i (1+ i)))
  (setq started (getvar "MILLISECS"))
  (chlay:deduplicate-hatches "PP_FORRO")
  (pp-test:emit "timing/hatch-first-ms" (- (getvar "MILLISECS") started))
  (setq started (getvar "MILLISECS"))
  (chlay:deduplicate-hatches "PP_FORRO")
  (pp-test:emit "timing/hatch-repeat-ms" (- (getvar "MILLISECS") started))
  (pp-test:snapshot "benchmark")
  (pp-test:clear)
  T
)
(defun pp-benchmark:run (output count / result)
  (setq *pp-test-output* (open output "w" "utf8"))
  (pp-test:emit "environment" (list (getvar "ACADVER") (getvar "LISPSYS")))
  (setq result (vl-catch-all-apply 'pp-benchmark:body (list count)))
  (if (vl-catch-all-error-p result)
    (pp-test:emit "fatal" (vl-catch-all-error-message result))
    (pp-test:emit "complete" T))
  (close *pp-test-output*) (setq *pp-test-output* nil)
  (princ)
)
