(defun c:test (/ c a d) 
  (vl-load-com)
  (vlax-for l (vla-get-layers (setq d (vla-get-activedocument (vlax-get-acad-object)))) 
    (cond ((= -1 (vlax-get l 'lock)) (vlax-put l 'lock 0) (setq a (cons l a))))
  )
  (vlax-for b (vla-get-blocks d) 
    (if (= 0 (vlax-get b 'isxref)) 
      (vlax-for o b 
        (cond 
          ((and (vlax-write-enabled-p o) (= (vla-get-objectname o) "AcDbHatch"))
           (or c 
               (progn (setq c (vla-get-backgroundcolor o)) 
                      (vla-put-entitycolor c -939524096)
               )
           )
           (vla-put-backgroundcolor o c)
          )
        )
      )
    )
  )
  (foreach l a (vlax-put l 'lock -1))
  (vla-regen d acallviewports)
  (princ)
)
